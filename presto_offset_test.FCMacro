# Isolation test: does makeOffsetShape survive on PrestoSolid? (may crash OCC)
# Run with PrestoSolid in the doc. FreeCAD 1.1.x.
import FreeCAD as App, Part
doc = App.ActiveDocument
P = doc.getObject("PrestoSolid")
if P is None or getattr(P, "Shape", None) is None or P.Shape.isNull():
    App.Console.PrintError("No PrestoSolid - run presto_build first.\n")
else:
    for nm in ("OffsetTest",):
        if doc.getObject(nm): doc.removeObject(nm)
    try:
        App.Console.PrintMessage("trying makeOffsetShape(3.0)...\n")
        off = P.Shape.makeOffsetShape(3.0, 0.01)
        o = doc.addObject("Part::Feature", "OffsetTest"); o.Shape = off
        try: o.ViewObject.Transparency = 60
        except Exception: pass
        doc.recompute()
        App.Console.PrintMessage(f"OFFSET OK  vol={off.Volume:.0f}  valid={off.isValid()}\n")
    except Exception as e:
        App.Console.PrintError(f"OFFSET raised (caught, no crash): {e}\n")
