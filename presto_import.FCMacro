# Presto profile -> exact-scaled Sketch -> extruded solid.
# FreeCAD 1.1.x.  Edit vars below, then Macro > Execute.
import FreeCAD as App, FreeCADGui as Gui, importSVG, Draft, Part

SVG        = "/Users/andrewhammond/dev/lotr-lcg-presto-hud/presto-side-profile-2mm.svg"
EXPECTED_W = 60.9    # mm bbox width  (side-2mm 60.9 / footprint 98.2)
EXPECTED_H = 73.2    # mm bbox height (side-2mm 73.2 / footprint 31.1)
EXTRUDE    = 92.22   # mm extrude depth (body width)

doc = App.ActiveDocument or App.newDocument("Presto")
# clear prior runs
for nm in ("PrestoSolid", "PrestoProfile", "PrestoEdges"):
    if doc.getObject(nm): doc.removeObject(nm)
doc.recompute()

before = set(doc.Objects)
importSVG.insert(SVG, doc.Name)
doc.recompute()
new = [o for o in doc.Objects if o not in before]

edges = []
for o in new:
    sh = getattr(o, "Shape", None)
    if sh and not sh.isNull(): edges += sh.Edges
if not edges:
    App.Console.PrintError("No geometry imported.\n"); raise SystemExit
comp = Part.makeCompound(edges)
bb = comp.BoundBox
App.Console.PrintMessage(f"Imported bbox: {bb.XLength:.3f} x {bb.YLength:.3f} mm\n")

# exact non-uniform scale to design size, moved to origin
kx = EXPECTED_W / bb.XLength if EXPECTED_W > 0 else 1.0
ky = EXPECTED_H / bb.YLength if EXPECTED_H > 0 else 1.0
mt = App.Matrix(); mt.move(App.Vector(-bb.XMin, -bb.YMin, 0))
ms = App.Matrix(); ms.scale(kx, ky, 1.0)
comp = comp.transformGeometry(ms.multiply(mt))
App.Console.PrintMessage(f"Final bbox: {comp.BoundBox.XLength:.3f} x {comp.BoundBox.YLength:.3f} mm\n")

for o in new: doc.removeObject(o.Name)
feat = doc.addObject("Part::Feature", "PrestoEdges"); feat.Shape = comp
doc.recompute()
sk = Draft.make_sketch([feat], autoconstraints=True, name="PrestoProfile")
doc.removeObject(feat.Name); doc.recompute()

# extrude the closed profile into a solid
ext = doc.addObject("Part::Extrusion", "PrestoSolid")
ext.Base = sk
ext.DirMode = "Custom"; ext.Dir = App.Vector(0, 0, 1)
ext.LengthFwd = EXTRUDE; ext.Solid = True
sk.Visibility = False
doc.recompute()

if not ext.Shape.isNull():
    App.Console.PrintMessage(f"Solid volume: {ext.Shape.Volume:.1f} mm^3\n")
Gui.activeDocument().activeView().viewAxonometric()
Gui.SendMsgToActiveView("ViewFit")
App.Console.PrintMessage("Done -> PrestoSolid extruded, view fitted.\n")
